(defun c:STRPLYT (/ OLD_OSM C1 C2 D1 NUM OB1 OB2 OB3 OB4 P1 P2 R1 R2 R3 SS)
  (setq old_osm (getvar "OSMODE"))
  (setvar "OSMODE" 0)
  (setq	r1  50.
	r2  15.
	r3  3.
	d1  30.
	num 4) ;; your input data?
  (setq	c1 '(0. 0. 0.)
	c2 (polar c1 0. d1)
	p1 (polar c1 (* pi 1.5) r3)
	p2 (polar c2 (* pi 0.5) r3)
  )
  (command "_.circle" c1 r1)
  (setq ob1 (entlast))
  (command "_.circle" c1 r2)
  (setq ob2 (entlast))
  (setq ss (ssadd))
  (ssadd ob2 ss)
  (command "_.rectang" p1 p2)
  (setq ob3 (entlast))
  (command "_.circle" c2 r3)
  (setq ob4 (entlast))
  (command "-array" ob2 ob3 ob4 "" "P" c1 num "360" "Y")
  (while (setq ob2 (entnext ob2))
    (ssadd ob2 ss)
  )
  (command "_.region" ss "")
  (setq ss nil)
  (setq ss (ssadd))
  (setq ob2 (entnext ob1))
  (ssadd ob2 ss)
  (while (setq ob2 (entnext ob2))
    (ssadd ob2 ss)
  )
  (command "_.union" ss "")
  (setq ob2 (entlast))
  (command "_.bhatch" "_P" "ANGLE" 1. 0. "_S" ob1 ob2 "" ""
  	   "_.bhatch" "_P" "ANSI31" 1. 0. "_S" ob2 "" "")
  (setvar "OSMODE" old_osm)
  (princ)
)
